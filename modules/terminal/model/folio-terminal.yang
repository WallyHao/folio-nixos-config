module folio-terminal {
  yang-version 1.1;
  namespace "urn:folio:terminal";
  prefix ft;
  import folio-environment { prefix fe; revision-date 2026-10-27; }

  organization "Folio";
  description "Terminal-owned settings, initially the user Foot contribution.";
  revision 2026-10-27 { description "Unified shared theme selection and environment dependency."; }
  revision 2026-10-24 { description "Add Yazi terminal file manager."; }
  revision 2026-10-22 { description "Move Git and GitHub CLI preferences into the terminal capability."; }
  revision 2026-10-21 { description "Add independently selectable shell and terminal utilities."; }
  revision 2026-10-20 { description "Express background opacity as a unit fraction instead of a percentage."; }
  revision 2026-10-19 { description "Add configurable background opacity in percent."; }
  revision 2026-10-18 { description "Foot settings independent of activation."; }

  augment '/fe:environment/fe:modules' {
    when "fe:name = 'terminal'";
    container terminal {
      presence "Terminal settings are supplied.";
      container git {
        when "../../../fe:scope = 'user'";
        leaf enabled { type boolean; default true; }
        leaf user-name { type string { length '1..256'; pattern '[^\r\n]+'; } }
        leaf user-email { type string { length '3..256'; pattern '[^\r\n]+'; } }
        leaf github-cli { type boolean; default true; }
        leaf default-branch { type string { pattern '[a-zA-Z][a-zA-Z0-9_/-]*'; } default main; }
        leaf pull-rebase { type boolean; default true; }
      }
      container shell {
        leaf enabled { type boolean; default true; }
        leaf prompt { type enumeration { enum simple; enum powerlevel10k; } default powerlevel10k; }
        leaf history-size { type uint32 { range '1..1000000'; } default 10000; }
        leaf completion { type boolean; default true; }
        leaf autosuggestions { type boolean; default true; }
        leaf syntax-highlighting { type boolean; default true; }
      }
      container tools {
        leaf yazi { type boolean; default true; }
        leaf bat { type boolean; default true; }
        leaf btop { type boolean; default true; }
        leaf eza { type boolean; default true; }
        leaf fd { type boolean; default true; }
        leaf fzf { type boolean; default true; }
        leaf jq { type boolean; default true; }
        leaf ripgrep { type boolean; default true; }
        leaf zoxide { type boolean; default true; }
        leaf unzip { type boolean; default true; }
        leaf unrar { type boolean; default true; }
        leaf chsrc { type boolean; default true; }
        leaf just { type boolean; default true; }
        leaf typst { type boolean; default true; }
      }
      container foot {
        leaf enabled { type boolean; default true; }
        leaf font {
          type string { length '1..256'; pattern '[^\r\n]+'; }
          description "Optional module override of resolved public font preferences.";
        }
        leaf padding { type string { pattern '[0-9]+x[0-9]+'; } default '15x15'; }
        leaf opacity {
          type decimal64 { fraction-digits 2; range '0..1'; }
          default '1';
          description "Background opacity as a unit fraction; 0.75 means 75 percent.";
        }
      }
    }
  }
}
